module ietf-schedule {
     yang-version 1.1;
     namespace "urn:ietf:params:xml:ns:yang:ietf-schedule";
     prefix schedule;
     
     import ietf-yang-types {
       prefix yang; 
       reference
         "RFC 6991: Common YANG Data Types";
     }
     organization
       "IETF OPSAWG Working Group";
     contact
       "WG Web: <https://datatracker.ietf.org/wg/opsawg/>
        WG List: <mailto:opsawg@ietf.org>";
     description
       "This YANG module defines two properties of an iSchedule 
        object:period of time and recurrence rule. 

        Copyright (c) 2023 IETF Trust and the persons identified
        as authors of the code. All rights reserved.

        Redistribution and use in source and binary forms, with
        or without modification, is permitted pursuant to, and
        subject to the license terms contained in, the Revised
        BSD License set forth in Section 4.c of the IETF Trust's
        Legal Provisions Relating to IETF Documents
        (https://trustee.ietf.org/license-info).

        This version of this YANG module is part of RFC XXXX
        (https://www.rfc-editor.org/info/rfcXXXX); see the RFC
        itself for full legal notices.";

     revision 2023-01-09 {
       description
         "Initial revision.";
       reference
         "RFC XXXX: A Policy-based Network Access Control";
     }

     typedef weekday {

       type enumeration {
         enum sunday {
           description
             "Sunday of the week.";
         }
         enum monday {
           description
             "Monday of the week.";
         }
         enum tuesday {
           description
             "Tuesday of the week.";
         }
         enum wednesday {
           description
             "Wednesday of the week.";
         }
         enum thursday {
           description
             "Thursday of the week.";
         }
         enum friday {
           description
             "Friday of the week.";
         }
         enum saturday {
           description
             "Saturday of the week.";
         }
       }
       description
         "Seven days of the week.";       
     }     
     
     grouping period {
       description
         "This grouping is defined for period of time property.";
       container period-of-time {
         description
           "This container is defined to identify period values that
            contain a precise period of time.";
         choice forms {
           description
             "Two forms of period of time.";
           case period-explicit {
             description
               "A period of time is identified by its start and its 
                end.";
             leaf explicit-start {
               type yang:date-and-time;
               description
                 "Period start time.";
             }
             leaf explicit-end {
               type yang:date-and-time;
               description
                 "Period end time.";
             }
           }
           case period-start {
             description
               "A period of time is defined by a start and a 
                positive duration of time.";
             leaf start {
               type yang:date-and-time;
               description
                 "Period start time.";
             }
             leaf duration {
               type yang:time-no-zone;
               description
                 "Duration of the time.";
             }
           }
         } 
       }  
     }
     grouping recurrence {
       description
         "This grouping is defined to identify properties that 
          contain a recurrence rule specification";
       container recurrence {
         description
           "Recurrence rule definition.";
         leaf freq {  
           type enumeration {
             enum secondly {
               value 1;
               description
                 "Repeating events based on an interval of a second
                  or more.";
             }
             enum minutely {
               value 2;
               description
                 "Repeating events based on an interval of a minute
                  or more.";
             }
             enum hourly {
               value 3;
               description
                 "Repeating events based on an interval of an hour
                  or more.";
             }
             enum daily {
               value 4;
               description
                 "Repeating events based on an interval of a day or
                  more.";
             }
             enum weekly {
               value 5;
               description
                 "Repeating events based on an interval of a week or
                  more.";
             }
             enum monthly {
               value 6;
               description
                 "Repeating events based on an interval of a month or
                  more.";
             }
             enum yearly {
               value 7;
               description
                 "Repeating events based on an interval of a year or
                  more.";
             }
           }
           mandatory true;
           description
             "This parameter is defined to identify the type of 
              recurrence rule.";
         }
         choice until-or-count { 
           description
             "Modes to bound the recurrence rule.";
           case until {
             description
               "This case defines a way that bounds the recurrence 
                rule in a inclusive manner.";
             leaf until {
               type union { 
                 type yang:date;
                 type yang:date-and-time;
               }
               description
                 "This parameter specifies a date or date-time value
                  to bounds the recurrence.";
             }
           }
           case count {
             description
               "This case defines the number of occurrences at which
                to range-bound the recurrence.";
             leaf count {
               type uint32;
               description
                 "The positive number of occurrences at which to 
                  range-bound the recurrence.";               
             }
           }
         }  
         leaf interval { 
           type uint32;
           default 1;
           description
             "A positive integer representing at which intervals the
              recurrence rule repeats.";
         }
         leaf-list bysecond { 
           type uint32 {
             range "0..60";
           }
           description
             "A list of seconds within a minute.";
         }
         leaf-list byminute {
           type uint32 {
             range "0..59";
           }
           description
             "A list of minutes within an hour.";
         }
         leaf-list byhour {
           type uint32 {
             range "0..23";
           }
           description
             "Specify a list of hours of the day.";
         }
         list byday {
           key "weekday";
           description
             "Specify a list of days of the week.";
           leaf direction {
             when "(enum-value(../../freq) >= 6) and "+
             "(enum-value(../../freq) = 7) and not(../../byyearweek)";
             type int32 {
               range "-53..-1|1..53";
             }
             description
               "When specified, it indicates the nth occurrence of a 
                specific day within the MONTHLY or YEARLY 'RRULE'.";
           }
           leaf weekday {
             type schedule:weekday;
             description
               "Corresponding to seven days of the week.";
           }
         }
         leaf-list bymonthday {
           type int32 {
             range "-31..-1|1..31";
           }
           description
             "Specify a list of days of the month.";       
         }
         leaf-list byyearday {
           type int32 {
             range "-366..-1|1..366";
           }
           description
             "Specify a list of days of the year.";
         }
         leaf-list byyearweek {
           when "enum-value(../freq)=7";
           type int32 {
             range "-53..-1|1..53";
           }
           description
             "Specify a list of weeks of the year.";
         }
         leaf-list byyearmonth {
           type uint32 {
             range "1..12";
           }
           description
             "Specify a list of months of the year.";
         }
         leaf-list bysetpos {
           type int32 {
             range "-366..-1|1..366";
           }
           description
             "Specify a list of values that corresponds to the nth 
              occurrence within the set of recurrence instances 
              specified by the rule.";
         }
         leaf-list wkst {
           type schedule:weekday;
           default monday;
           description
             "Specify the day on which the workweek starts.";
         }     
       }
     }
   }
