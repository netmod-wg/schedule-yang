module example-sch-capacity-res {
  yang-version 1.1;
  namespace "http://example.com/example-sch-capacity-res";
  prefix "ex-schecaparev";

  import ietf-network-topology {
    prefix "nt";
  }

  import ietf-schedule {
    prefix "schedule";
  }

  organization
    "Example, Inc.";

  contact
    "Support at example.com";

  description
    "An example to show a scheduled link capacity reservation.";

  revision "2026-02-20" {
    description
      "Initial version.";
    reference
      "RFC 9922: A YANG Data Model for Scheduling";
  }

  container link-capability-reservations {
    description
      "A container for a scheduled link capability reservations";
    list scheduled-link-capacity {
      key "schedule-id";
      description
        "Definition of scheduled link capacity list";
      leaf schedule-id {
        type string;
        description
          "The schedule identifier for this schedule rule.";
      }
      leaf link-id {
        type nt:link-id;
        description
          "The identifier of a link in the topology.";
      }
      leaf reserved-capability {
        type uint64;
        units "Mbps";
        description
          "The reserved capability for a particular link.";
      }
      uses schedule:period-of-time;
    }
  }
}
